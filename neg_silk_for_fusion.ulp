#usage "<h3>Inverted Silkscreen</h3>"
 "First create your art work (polygon in layer 1 \"Top\" with text inside it on layer 41 \"RestrictTop\" <b>with vector font type</b>).<br>"
 "NOTE: Choose \"Polygon\" and not \"Polygon Shape\".<br>"
 "Click on \"Re-fill Polygon Pours\" if needed.<br>"
 "Name the polygon with \"NEG_SILK\" to make it special from other normal polygons.<br>"
 "Run the ULP.<br><br>"
 "<author>Authors: Christian Bohrer (Original), Yahya Tawil (Enhancment), Romain Lamothe (Autodesk Fusion port)</author>"


 // THIS PROGRAM IS PROVIDED AS IS AND WITHOUT WARRANTY OF ANY KIND, EXPRESSED OR IMPLIED
 /*
 First Create by: Christian Bohrer (negasilk.ulp)
 Edited by Yahya Tawil 2017 (neg_silk.ulp) Documentation: https://atadiat.com/en/e-negative-silkscreen-eagle-ulp/
 Edited by Yahya Tawil 2020 Assert on polygon width zero to avoid zero width case which will result a long filling loop
 Edited by Romain Lamothe 2024 Autodesk Fusion port
 */

// For Fusion, it should be +9.7.x
int version = EAGLE_VERSION; // 9
int release = EAGLE_RELEASE; // 7

if(version == 9)
{
  if(release <= 6) // The last standalone version of EAGLE is 9.6.2
  {
    dlgMessageBox("This ULP is for Autodesk Fusion; for standalone Eagle, use neg_silk.ulp.","+OK");
  }
}
else if(version < 9) // older versions
{
    dlgMessageBox("This ULP is for Autodesk Fusion; for standalone Eagle, use neg_silk.ulp.","+OK");
}

string CMD = "SET WIRE_BEND 2;\n"; // Wire bend 2 = Straight connection
CMD += "LAYER 21;\n"; // Go to layer SilkscreenTop
CMD += "DISPLAY NONE 21;\n"; // Only show SilkscreenTop
CMD += "GRID MM;\n"; // Set the grid units to mm

int found = 0;
if(board) board(B) {    
  B.signals(S) {   
    if(S.name == "NEG_SILK") {
      found = 1;
      S.polyPours(P) {
        if(P.width == 0) { // zero size polygon will make an infinit loop with P.fillings loop member
          dlgMessageBox("!Change \"NEG_SILK\" width to any value bigger than Zero.","+OK");
          exit(-1);	
        }
        else {
          P.fillings(W){
            if(W.layer == 1) {
              string trace_line_cmd;
              sprintf(trace_line_cmd,"LINE %3.4f (%3.4f %3.4f) (%3.4f %3.4f);\n", u2mm(W.width), u2mm(W.x1), u2mm(W.y1), u2mm(W.x2), u2mm(W.y2));
              CMD += trace_line_cmd;
            }
          }
        }
      }
    }
  }
  if(!found) {
    dlgMessageBox("!No Polygon with signal name \"NEG_SILK\" is found","+OK");
    exit(-1);
  }
  exit(CMD);

} else dlgMessageBox("!This ULP can only be executed in the PCB window.","+OK");
